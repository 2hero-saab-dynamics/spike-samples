# Ground-station telemetry relay requirements
Invented sample for the Spiking Lab. Ground-station telemetry relay. Not a real system.

# Specification: Ground-station telemetry relay

## GSR-REQ-001
The relay shall reject any telemetry frame whose CRC-16 trailer does not match the frame payload, and shall not forward a rejected frame.

## GSR-REQ-002
The relay shall stamp each received frame with the UTC time of reception, to millisecond resolution, before any other processing.

## GSR-REQ-003
While the downstream link is unavailable, the relay shall buffer up to 10 000 frames and, when the link returns, forward them in order of reception.

## GSR-REQ-004
The relay shall drop from the buffer any frame older than 300 seconds, and shall log each dropped frame with its sequence number.

## GSR-REQ-005
The relay shall load its configuration only if the configuration file carries a valid signature from the operator's key; otherwise it shall refuse to start.

## GSR-REQ-006
The relay shall provide a health endpoint that reports buffer occupancy, downstream link state and seconds since the last received frame.

## GSR-REQ-007
The relay shall write every operator command, with its outcome, to the audit log before the command's effect is applied.

## GSR-REQ-008
The relay shall forward at most 500 frames per second to the downstream link and shall queue, not drop, any excess.
